module detnet-qos-template-api {
	namespace "urn:detnet:qos-template-api";
	prefix "detnet-qos-template-api";
	
	organization "zte";
	description
       "This module defines the northbound interface for Detnet .";
	revision 2018-09-06 {
		description "Initial revision.";
	}
		
	import detnet-qos-template {
		prefix "detnet-qos-template";
	}	
	import detnet-common {
		prefix "detnet-common";
	}

	rpc config-mapping-template {
		input {
			leaf template-name {
				type string;
			}
			uses detnet-qos-template:priority-mapping-group;
		}		
		output {
			uses detnet-common:configure-result;
		}
	}

	rpc delete-mapping-template {
		input {
			leaf template-name {
				type string;
			}
		}
		output {
			uses detnet-common:configure-result;
		}
	}

    rpc query-mapping-template {
        input {
            leaf template-name {
                type string;
            }
        }
        output {
            uses detnet-qos-template:priority-mapping-group;
        }
    }
}
