module ieee802-types {

    yang-version 1;

    namespace
      "urn:ieee:std:802.1Q:yang:ieee802-types";

    prefix ieee;

    organization
      "Institute of Electrical and Electronics Engineers";

    contact
      "WG-URL: http://grouper.ieee.org/groups/802/1/
    WG-EMail: stds-802-1@ieee.org

    Contact: IEEE 802.1 Working Group Chair
    Postal: C/O IEEE 802.1 Working Group
            IEEE Standards Association
            445 Hoes Lane
            P.O. Box 1331
            Piscataway
            NJ 08855-1331
            USA

    E-mail: STDS-802-1-L@LISTSERV.IEEE.ORG";

    description
      "This module contains a collection of generally useful derived
    data types for IEEE YANG models.";

    revision "2017-07-20" {
      description
        "Updates based upon comment resolution on draft
      D1.1 of P802.1Qcp.";
      reference
        "IEEE 802.1Q-2017, Media Access Control (MAC) Bridges and
        Virtual Bridged Local Area Networks.";

    }


    typedef mac-address {
      type string {
        pattern
          '[0-9a-fA-F]{2}(-[0-9a-fA-F]{2}){5}';
      }
      description
        "The mac-address type represents a MAC address in the canonical
      format and hexadecimal format specified by IEEE Std 802.
    	The hexidecimal representation uses uppercase characters.";
      reference
        "IEEE 802-2014, Clauses 3.1, 8.1";

    }

    typedef vlanid {
      type uint16 {
        range "1..4094";
      }
      description
        "The vlanid type uniquely identifies a VLAN. This is the 12-bit
      VLAN-ID used in the VLAN Tag header. The range is defined by
      the referenced specification. This type is in the value set and
      its semantics equivalent to the VlanId textual convention of
      the SMIv2.";
      reference
        "IEEE Std 802.1Q-2017: Virtual Bridged Local Area Networks.";

    }
  }
