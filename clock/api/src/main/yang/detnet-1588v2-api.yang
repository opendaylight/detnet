module detnet-1588v2-api {
	namespace "urn:detnet:1588v2-api";
	prefix "detnet-1588v2-api";
	
	organization "zte";
	description
       "This module defines the northbound interface for Detnet 1588v2.";
	revision 2018-09-04 {
		description "Initial revision.";
	}
	
	import detnet-1588v2 {
		prefix "detnet-1588v2";
	}
	
	import detnet-common {
		prefix "detnet-common";
	}
	
	rpc config-1588v2-ds {
		input {
			leaf node-id {
				type string;
			}
			leaf instance-number {
				type uint16;
			}
			container default-ds-input {
			    uses detnet-1588v2:default-ds-entry;
			}
			leaf clock-identity {
			    type string;
			}
		}
		output {
			uses detnet-common:configure-result;
		}
	}

	rpc config-1588v2-time-properties-ds {
	    input {
            leaf node-id {
                type string;
            }
            leaf instance-number {
                type uint16;
            }
            container time-properties-input {
                uses detnet-1588v2:time-properties-ds-entry;
            }
        }
        output {
            uses detnet-common:configure-result;
        }
	}
	
	rpc config-1588v2-port-ds {
		input {
			leaf node-id {
				type string;
			}
			leaf instance-number {
				type uint16;
			}
			leaf port-number {
				type uint16;
			}
			container port-ds-input {
			    uses detnet-1588v2:port-ds-entry;
			}
			leaf clock-identity {
                type string;
            }
		}
		output {
			uses detnet-common:configure-result;
		}
	}
	
	rpc delete-1588v2-ds {
		input {
			leaf node-id {
				type string;
			}
			leaf instance-number {
				type uint16;
			}
		}
		output {
			uses detnet-common:configure-result;
		}
	}
	rpc delete-1588v2-port-ds {
		input {
			leaf node-id {
				type string;
			}
			leaf instance-number {
				type uint16;
			}
			leaf port-number {
				type uint16;
			}
		}
		output {
			uses detnet-common:configure-result;
		}
	}

	rpc delete-1588v2-time-properties {
	    input {
            leaf node-id {
                type string;
            }
            leaf instance-number {
                type uint16;
            }
        }
        output {
            uses detnet-common:configure-result;
        }
	}

	rpc query-1588v2-node-config {
	    input {
	        leaf node-id {
                type string;
            }
	    }

	    output {
	        list instance-list-output {
	            uses detnet-1588v2:instance-list-group;
	            leaf clock-identity {
	                type string;
	            }
	        }
	        uses detnet-common:configure-result;
	    }
	}

}
